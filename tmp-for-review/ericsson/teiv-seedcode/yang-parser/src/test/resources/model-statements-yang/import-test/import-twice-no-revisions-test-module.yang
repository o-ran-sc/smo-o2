module import-twice-no-revisions-test-module {

    namespace "test:import-twice-no-revisions-test-module";
    prefix "this";

	description
	"Copyright (C) 2024 Ericsson
	Modifications Copyright (C) 2024 OpenInfra Foundation Europe";

    revision "2020-10-02" {
        description "initial revision";
    }

	import ietf-yang-metadata {
		prefix prefix1;
	}

	import ietf-yang-metadata {
		prefix prefix2;
	}

}
