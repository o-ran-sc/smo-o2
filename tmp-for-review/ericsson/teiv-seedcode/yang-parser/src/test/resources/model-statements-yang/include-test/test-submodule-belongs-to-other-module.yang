submodule test-submodule {

	yang-version "1.1";

	belongs-to some-other-module {
		prefix this;
	}

	description
	"Copyright (C) 2024 Ericsson
	Modifications Copyright (C) 2024 OpenInfra Foundation Europe";

    revision "2020-10-02" {
        description "initial revision";
    }

}
