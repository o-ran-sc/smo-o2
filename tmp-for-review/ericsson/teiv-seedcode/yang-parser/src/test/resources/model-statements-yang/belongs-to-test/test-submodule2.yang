submodule test-submodule2 {

	belongs-to test-submodule {
		prefix this;
	}

	description
	"Copyright (C) 2024 Ericsson
	Modifications Copyright (C) 2024 OpenInfra Foundation Europe";

    revision "2020-10-02" {
        description "initial revision";
    }

}
