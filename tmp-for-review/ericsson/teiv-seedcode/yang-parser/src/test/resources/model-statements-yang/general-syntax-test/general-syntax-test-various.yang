module general-syntax-test-various {

    namespace "test:general-syntax-test-various";
    prefix this;

	description
	"Copyright (C) 2024 Ericsson
	Modifications Copyright (C) 2024 OpenInfra Foundation Europe";

    revision "2020-07-22" {
        description "Initial revision";
    }

	// - - - - enums - - - - -

	container cont1 {
		leaf leaf1 {
			type enumeration {
				enum zero {
					value 0;
				}
				enum one {
					status deprecated;
				}
				enum two;

				enum "thr ee";		// Whitespace

				enum "fo.ur";		// OK

				enum "fi/ve";		// Weird characters

				enum six {
					value;			// Omitted value
				}

				enum seven {
					value "Hello!";	// not numeric
				}
			}
		}
	}

 	// - - - - status - - - - -

    container cont2 {

    	leaf leaf11 {
    		type string;
    		status current;
    	}

    	leaf leaf12 {
    		type string;
    		status deprecated;
    	}

    	leaf leaf13 {
    		type string;
    		status obsolete;
    	}

    	leaf leaf14 {
    		type string;
    		status blurb;
    	}

    	leaf leaf15 {
    		type string;
    		status;
    	}
    }

    // - - - - - container - - - - -

    container cont3 {

    	grouping grouping1 {
    		leaf leaf21 {
    			type uint16;
    		}
    	}

    	typedef typedef1 {
    		type boolean;
    	}

    	leaf leaf22 {
    		type uint16;
    	}

    	leaf leaf23 {
    		type uint16;
    	}

    	choice choice1 {
    		case case1 {
    			leaf leaf24 {
    				type string;
    			}
    		}
    		case case2 {
    			leaf leaf25 {
    				type string;
    			}
    		}
    	}

    	list list1 {
    		key "name";
    		leaf name {
    			type string;
    		}
    	}

    	notification notification1 {
   			leaf leaf26 {
   				type string;
   			}
    	}

    	leaf-list leaflist1 {
    		type uint32;
    	}

    	anydata anydata1;
    	anydata anydata2;

		anyxml anyxml1;
		anyxml anyxml2;
		anyxml anyxml3;
    }

    // - - - - - choice and case - - - - -

    choice choice1 {
		when "../cont3";
		status deprecated;

		config true;
		default case2;

    	leaf leaf27 {
    		type uint16;
    	}

    	leaf leaf28 {
    		type uint16;
    	}

    	list list4 {
    		key "name";
    		leaf name {
    			type string;
    		}
    	}

    	leaf-list leaflist1 {
    		type uint32;
    	}

    	anydata anydata1;
		anyxml anyxml1;
		anyxml anyxml2;

		case case2 {
			when "../cont2";
			status obsolete;

			leaf leaf29 {
				type string;
			}

			leaf-list leaflist3 {
				type int32;
			}

		   	anydata anydata1;

			anyxml anyxml1;
			anyxml anyxml2;
		}
    }

    // - - - - - list - - - - -

    list list4 {

    	key leaf22;
    	config true;
    	ordered-by system;
    	status current;

    	grouping grouping1 {
    		leaf leaf21 {
    			type uint16;
    		}
    	}

    	typedef typedef1 {
    		type boolean;
    	}

    	action action1;
    	action action2;
    	action action3;

    	leaf leaf22 {
    		type uint16;
    	}

    	leaf leaf23 {
    		type uint16;
    	}

    	choice choice1 {
    		case case1 {
    			leaf leaf24 {
    				type string;
    			}
    		}
    		case case2 {
    			leaf leaf25 {
    				type string;
    			}
    		}
    	}

    	list list1 {
    		key "name";
    		leaf name {
    			type string;
    		}
    	}

    	notification notification1 {
   			leaf leaf26 {
   				type string;
   			}
    	}

    	leaf-list leaflist1 {
    		type uint32;
    	}

    	anydata anydata1;
    	anydata anydata2;

		anyxml anyxml1;
		anyxml anyxml2;
		anyxml anyxml3;
    }

    // - - - - - leaf-list - - - - -

	container cont5 {

		leaf-list leaflist51 {
			type string;
			ordered-by user;
		}

		leaf-list leaflist52 {
			type string;
			ordered-by system;
		}

		leaf-list leaflist53 {
			type string;
			ordered-by something-else;
		}

		leaf-list leaflist54 {
			type string;
			ordered-by;
		}
	}
}
