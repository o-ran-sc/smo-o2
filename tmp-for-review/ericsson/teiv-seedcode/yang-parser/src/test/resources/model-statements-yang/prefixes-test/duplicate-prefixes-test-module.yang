module duplicate-prefixes-test-module {

	namespace "test:duplicate-prefixes-test-module";
	prefix "this";

	description
	"Copyright (C) 2024 Ericsson
	Modifications Copyright (C) 2024 OpenInfra Foundation Europe";

	revision "2020-10-02" {
		description "initial revision";
	}

	import ietf-origin {
		prefix prefix1;
	}

	import ietf-yang-metadata {
		prefix prefix1;
	}
}
