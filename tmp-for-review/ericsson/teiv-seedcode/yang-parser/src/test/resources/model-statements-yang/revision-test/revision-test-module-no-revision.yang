module revision-test-module {

	namespace "test:revision-test-module";
	prefix "this";

	description
	"Copyright (C) 2024 Ericsson
	Modifications Copyright (C) 2024 OpenInfra Foundation Europe";

	container cont1 {
		leaf leaf1 {
			type uint32;
		}
	}
}
