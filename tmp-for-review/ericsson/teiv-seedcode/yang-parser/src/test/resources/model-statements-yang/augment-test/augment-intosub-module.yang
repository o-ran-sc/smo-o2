module augment-intosub-module {

    namespace "test:augment-intosub-module-test";
    prefix module;

	description
	"Copyright (C) 2024 Ericsson
	Modifications Copyright (C) 2024 OpenInfra Foundation Europe";

    revision "2020-12-10";

	include augment-intosub-submodule;

	container cont1;



}
