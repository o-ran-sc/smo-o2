module submodule-test-module {

    namespace "urn:o-ran:yang:submodule-test-module";
    prefix this;

	description
	"Copyright (C) 2024 Ericsson
	Modifications Copyright (C) 2024 OpenInfra Foundation Europe";

    include submodule-test-submodule {
        revision-date "1999-09-09";		// does not exist
    }

    revision "2020-06-09" {
        description "Initial revision";
    }

    container cont1 {
        leaf leaf11 {
            type string;
        }
    }

    uses grouping1;
}
