module revision-test-module {

    namespace "test:revision-test-module";
    prefix "this";

	description
	"Copyright (C) 2024 Ericsson
	Modifications Copyright (C) 2024 OpenInfra Foundation Europe";

    revision "2019-09-27" {
        description "lates revision with copy/paste error";
    }

    revision "2019-09-27" {
        description "in-between revision";
    }

    revision "2018-05-05" {
        description "initial revision";
    }

    container cont1 {
        leaf leaf1 {
            type uint32;
        }
    }
}
