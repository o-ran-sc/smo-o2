module import-itself-test-module {

    namespace "test:import-twice-first-no-revision-test-module";
    prefix "this";

	description
	"Copyright (C) 2024 Ericsson
	Modifications Copyright (C) 2024 OpenInfra Foundation Europe";

    revision "2020-10-02" {
        description "initial revision";
    }

	import import-itself-test-module {
		prefix prefix1;
		revision-date 2020-10-02;
	}

}
