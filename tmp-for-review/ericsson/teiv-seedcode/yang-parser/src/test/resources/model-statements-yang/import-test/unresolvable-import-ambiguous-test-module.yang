module unresolvable-import-ambiguous-test-module {

	namespace "test:unresolvable-import-ambiguous-test-module";
	prefix "this";

	description
	"Copyright (C) 2024 Ericsson
	Modifications Copyright (C) 2024 OpenInfra Foundation Europe";

	revision "2020-10-02" {
		description "initial revision";
	}

	import ietf-yang-types {
		prefix prefix1;
	}
}
