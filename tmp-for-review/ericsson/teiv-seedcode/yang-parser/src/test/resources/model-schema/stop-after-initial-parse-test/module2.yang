module module2 {

    namespace "test:module2";
    prefix this;

	description
	"Copyright (C) 2024 Ericsson
	Modifications Copyright (C) 2024 OpenInfra Foundation Europe";

    revision "2020-01-01" {
        description "initial revision";
    }

    grouping grouping1 {

    	leaf leaf99 {
    		type boolean;
    	}
    }
}
