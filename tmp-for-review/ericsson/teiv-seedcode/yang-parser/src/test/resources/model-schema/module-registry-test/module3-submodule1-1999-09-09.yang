submodule module3-submodule1 {

    belongs-to module3 {
        prefix mod3;
    }

    revision "1999-09-09" {
        description "initial revision";
    }

	description
	"Copyright (C) 2024 Ericsson
	Modifications Copyright (C) 2024 OpenInfra Foundation Europe";

}
