submodule submodule4 {

	belongs-to module1 {
		prefix mod1;
	}

	description
	"Copyright (C) 2024 Ericsson
	Modifications Copyright (C) 2024 OpenInfra Foundation Europe";

	import module2 {
		prefix mod2;
	}

	import module3 {
		prefix mod3;
	}

    revision "2020-09-30" {
        description "initial revision";
    }
}
