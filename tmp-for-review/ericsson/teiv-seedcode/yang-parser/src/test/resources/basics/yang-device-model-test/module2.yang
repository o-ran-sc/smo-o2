module module2 {

    namespace "urn:module2";
    prefix this;

	description
	"Copyright (C) 2024 Ericsson
	Modifications Copyright (C) 2024 OpenInfra Foundation Europe";

    revision "2020-12-04";

	grouping grouping1 {
		leaf leaf1 {
			type string;
		}
	}

	typedef typedef1 {
		type uint32;
	}

}
