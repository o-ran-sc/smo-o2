module module1 {

    namespace "test:module1";
    prefix this;

    description
    "Copyright (C) 2024 Ericsson
    Modifications Copyright (C) 2024 OpenInfra Foundation Europe";

    revision "2020-01-01" {
        description "initial revision";
    }
}
