module missing-include-name {
	yang-version 1.0;

    namespace "test:missing-include-name";

    prefix "this";

	description
	"Copyright (C) 2024 Ericsson
	Modifications Copyright (C) 2024 OpenInfra Foundation Europe";

    revision "2019-09-27";

    include;		// name missing

    container cont1;

}
