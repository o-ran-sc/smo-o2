// line comment
// line comment
module line-comment-module {
    namespace "test-module";
    prefix "this";

	description
	"Copyright (C) 2024 Ericsson
	Modifications Copyright (C) 2024 OpenInfra Foundation Europe";

    revision "2019-09-27";
} // line comment
// line comment
// line comment
