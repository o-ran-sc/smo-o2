module basic-empty-module {
	yang-version 1.0;

    namespace "test:basic-empty-module";

    prefix "this";

	description
	"Copyright (C) 2024 Ericsson
	Modifications Copyright (C) 2024 OpenInfra Foundation Europe";

    revision "2019-09-27";
}
