module basic-module-including {
	yang-version 1.0;

    namespace "test:basic-module-including";

    prefix "this";

	description
	"Copyright (C) 2024 Ericsson
	Modifications Copyright (C) 2024 OpenInfra Foundation Europe";

    revision "2019-09-27";

    include basic-submodule;
}
