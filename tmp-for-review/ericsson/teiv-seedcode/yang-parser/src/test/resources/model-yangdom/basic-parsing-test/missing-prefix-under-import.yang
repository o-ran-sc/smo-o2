module missing-prefix-under-import {
	yang-version 1.0;

    namespace "test:missing-prefix-under-import";

    prefix "this";

	description
	"Copyright (C) 2024 Ericsson
	Modifications Copyright (C) 2024 OpenInfra Foundation Europe";

    revision "2019-09-27";

    import basic-empty-module;

    container cont1;

}
