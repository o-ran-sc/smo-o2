module missing-yangversion-version {
	yang-version;

	namespace "test:missing-yangversion-version";

	prefix this;

	description
	"Copyright (C) 2024 Ericsson
	Modifications Copyright (C) 2024 OpenInfra Foundation Europe";

    revision "2019-09-27";
}
