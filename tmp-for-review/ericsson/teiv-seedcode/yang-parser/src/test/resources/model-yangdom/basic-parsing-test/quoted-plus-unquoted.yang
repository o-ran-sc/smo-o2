module quoted-plus-unquoted {

    namespace "quoted-plus-unquoted";
    prefix "this";

	description
	"Copyright (C) 2024 Ericsson
	Modifications Copyright (C) 2024 OpenInfra Foundation Europe";

    revision "2019-09-27";

	leaf leaf2 {
		type string;
		description "Hello" + World;
	}

}
