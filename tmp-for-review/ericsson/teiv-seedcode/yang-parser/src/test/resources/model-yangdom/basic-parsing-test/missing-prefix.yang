module missing-prefix {
	yang-version 1.0;

    namespace "test:missing-prefix";

	description
	"Copyright (C) 2024 Ericsson
	Modifications Copyright (C) 2024 OpenInfra Foundation Europe";

    revision "2019-09-27";
}
