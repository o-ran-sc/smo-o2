module dangling-block-comment {
    namespace "test-module";
    prefix "this";
	description
	"Copyright (C) 2024 Ericsson
	Modifications Copyright (C) 2024 OpenInfra Foundation Europe";
    revision "2019-09-27";
}/*

This block comment is not closed
