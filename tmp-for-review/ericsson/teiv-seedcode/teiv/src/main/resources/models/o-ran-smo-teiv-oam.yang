module o-ran-smo-teiv-oam {
    yang-version 1.1;
    namespace "urn:o-ran:smo-teiv-oam";
    prefix or-teiv-oam;

    import o-ran-smo-teiv-common-yang-types {prefix or-teiv-types; }

    import o-ran-smo-teiv-common-yang-extensions {prefix or-teiv-yext; }

    organization "ORAN";
    contact "The Authors";
    description 
    "RAN O&M topology model.

    Copyright (C) 2024 Ericsson
    Modifications Copyright (C) 2024 OpenInfra Foundation Europe

    This model contains the topology entities and relations in the
    RAN O&M domain, which are intended to represent management systems
    and management interfaces.";

    revision "2024-05-02" {
        description "Initial revision.";
        or-teiv-yext:label 0.3.0;
    }

    or-teiv-yext:domain OAM;

    list ManagedElement {
        description "A Managed Element (ME) is a node into a telecommunication network
                    providing support and/or service to subscribers. An ME communicates
                    with a manager application (directly or indirectly) over one or more
                    interfaces for the purpose of being monitored and/or controlled.";

        uses or-teiv-types:Top_Grp_Type;
        key id;

        container attributes {
            leaf fdn {
                description "This Full Distinguished Name (FDN) identifies
                            an instance of the ManagedElement MO. It contains
                            the full path from the Subnetwork to the
                            ManagedElement.";
                type or-teiv-types:_3GPP_FDN_Type;
            }

            container cmId {
                uses or-teiv-types:CM_ID;
            }
        }
    }
}
